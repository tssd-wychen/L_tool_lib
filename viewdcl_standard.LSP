(defun c:viewdcl()
  (setq dia003_l '("ACC" "ER" "OUP"))
  (setq dia004_l '(("1" "2" "3") ("A" "B" "C") ("a" "b" "c")))
  (if(not (setq dcl_file (getfiled "打开DCL文件" "" "DCL" 2)))(exit))
  (princ "DCL文件名：")(princ dcl_file)
  (if(not (setq dia_name (getstring "\n Dialog对话框名")))(exit))
  (if(< (setq dcl_id (load_dialog dcl_file)) 0)(exit))
  (if (null dcl_pt)(setq dcl_pt '(-1 -1)));(setq dcl_pt '(100 100))
  (if(not (new_dialog dia_name dcl_id "" dcl_pt))(exit))
  (start_list "dia003")(mapcar 'add_list dia003_l)(end_list)
  (start_list "dia004")(mapcar 'add_list (nth 0 dia004_l))(end_list)
  (action_tile "dia003" "(setq i_c (atoi $value))(>MOD_IN_DCL)(>GET_FROM_DCL)")
  (action_tile "dia004" "(setq i_r (atoi $value))(>GET_FROM_DCL)")
  (action_tile "accept" "(>GET_FROM_DCL)(done_dialog 1)")
  (action_tile "cancel" "(done_dialog 0)")
  (setq dd (start_dialog));princ...一句可为子程序入口
  (cond ((= dd 1) (princ "\n 确定<OK>!!!"))
	((= dd 0) (princ "\n 取消<Cancel>!!!"))
	(T (exit))
  )
  (prin1)
  
)
(defun >GET_FROM_DCL()
  (if i_c
    (setq dia003_res (nth i_c dia003_l))
  )
  (if (and i_c i_r)
    (setq dia004_res (nth i_r (nth i_c dia004_l)))
  )
)
(defun >MOD_IN_DCL()
  (cond
    ((= i_c 0)(start_list "dia004" 3)(mapcar 'add_list (nth 0 dia004_l))(end_list))
    ((= i_c 1)(start_list "dia004" 3)(mapcar 'add_list (nth 1 dia004_l))(end_list))
    ((= i_c 2)(start_list "dia004" 3)(mapcar 'add_list (nth 2 dia004_l))(end_list))
    (t (start_list "dia004")(mapcar 'add_list (nth 0 dia004_l))(end_list))
  )
)
