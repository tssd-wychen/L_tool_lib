(defun ax:DrawVpBorder (vp / ll ur coords pl)
  (vl-load-com)
  (setq vp (vlax-ename->vla-object vp))
  (vla-GetBoundingBox vp 'll 'ur)
  (setq	ll     (trans (vlax-safearray->list ll) 3 2)
	ur     (trans (vlax-safearray->list ur) 3 2)
	coords (vlax-safearray-fill
		 (vlax-make-safearray vlax-vbDouble (cons 0 7))
		 (list (nth 0 ll)
		       (nth 1 ll)
		       (nth 0 ur)
		       (nth 1 ll)
		       (nth 0 ur)
		       (nth 1 ur)
		       (nth 0 ll)
		       (nth 1 ur)
		 )
	       )
  )
  (vla-put-closed
    (setq pl (vla-AddLightWeightPolyline
	       (vla-get-ModelSpace (vla-get-Document vp))
	       coords
	     )
    )
    :vlax-true
  )
  (vlax-vla-object->ename pl)
)

(vl-load-com)
(defun c:tt (/ ENT LL LLPT LST MT PL SSN UR URPT VLAOBJ VP)
  (setvar 'CTAB "model")
  (setq lst (layoutlist))
  (foreach x lst
    (setvar 'CTAB x)
    (command "_.zoom" "_E")
    (if        (and (setq vp (ssget "x"
                             (list '(0 . "viewport")
                                   (cons 410 x)
                                   '(-4 . "/=")
                                   '(69 . 1)
                             )
                      )
             )
             (= (sslength vp) 1)
        )
      (progn (setq ssn          (ssname vp 0)
                   ent          (entget ssn)
                   VlaObj (vlax-ename->vla-object ssn)
             )
             (vlax-invoke-method VlaObj 'GetBoundingBox 'll 'ur)
             (setq llpt        (vlax-safearray->list ll)
                   urpt        (vlax-safearray->list ur)
             )
             (command "_.rectang" "_NONE" llpt "_NONE" urpt)
             (setq pl (entlast))
             (entmake (list '(0 . "MTEXT")
                            '(100 . "AcDbEntity")
                            '(100 . "AcDbMText")
                            (cons 10 llpt)
                            (cons 1 x)
                      )
             )
             (setq mt (entlast))
             (command "_.chspace" pl mt "")
             (command "_.pspace")
      )
    )
  )
  (setvar 'CTAB "model")
  (princ)
)
